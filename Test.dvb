Attribute VB_Name = "Module1"
Public Sub Testing()
    Dim myVBE As VBE
    Set myVBE = Application.VBE
   
    Application.LoadDVB ("C:\Users\Aaron\Source\Repos\VBATesting\Template1.dvb")
    
    
'    Dim vbaRef As VBProject
'    For Each vbaRef In myVBE.VBProjects
'        MsgBox vbaRef.Name & " " & vbaRef.Saved
'
'        If vbaRef.Name = "TemplateVBProject" Then
'            vbaRef.SaveAs ("c:\dill.vdb")
'
'        End If
'
'
'
'
'    Next
    Dim test1 As VBProject
    Dim test As VBIDE.VBProjects

    'Set test1 = myVBE.VBProjects.Add(vbext_pt_StandAlone)
    'test1.SaveAs ("c:\blah.dvb")
    
    MsgBox myVBE.ActiveVBProject.Saved
    myVBE.CommandBars("Standard").FindControl(, 3, , True, False).Execute
    MsgBox myVBE.ActiveVBProject.Saved
    
End Sub
